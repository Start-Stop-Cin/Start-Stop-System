# requirements_Software_Low_Level

## requirements_Software_Low__Level!Planilha1: References to requirements_Software_Low__Level.xlsx (Planilha1) (Container)
Read-only references to Microsoft Excel document.

### SW-LL-FR-01: Engine Stop - Enable (Functional)
The software must set EngineStopRequest =TRUE when SS_Enabled == TRUE AND GearPosition == D AND BrakeStatus == PRESSED (BrakePedalPosition ≥ 5%) AND VehicleSpeed ≤ 5 km/h AND AutostopAllowed ==TRUE.

### SW-LL-FR-02: Engine Stop - Enable (Functional)
The software must allow AutostopAllowed = TRUE when SpeedThresholdReached == TRUE, where SpeedThresholdReached is set when VehicleSpeed > 8 km/h is detected in the current drive cycle

### SW-LL-FR-03: Engine Stop - Inhibition (Functional)
The software must set AutostopAllowed = FALSE when GearPosition != D

### SW-LL-FR-04: Engine Stop - Inhibition (Functional)
The software must set AutostopAllowed = FALSE when InclinationAngle > INCLINATION_THRESHOLD (15%)

### SW-LL-FR-05: Engine Stop - Inhibition (Functional)
The software must set AutostopAllowed = FALSE when DoorStatus != CLOSED

### SW-LL-FR-06: Engine Stop - Inhibition (Functional)
The software must set AutostopAllowed = FALSE when SeatbeltStatus != FASTENED

### SW-LL-FR-07: Engine Restart - Autostart (Functional)
The software must set EngineRestartRequest = TRUE when AutostopActive == TRUE AND AcceleratorStatus == PRESSED (WHEN Accelerator PedalPosition > 5%)

### SW-LL-FR-08: Engine Restart - Autostart (Functional)
The software must set EngineRestartRequest = TRUE when AutostopActive == TRUE AND BrakeStatus == RELEASED (WHEN BrakePedalPosition < 5%)

### SW-LL-FR-09: Engine Restart - Autostart (Functional)
The software must set EngineRestartRequest = TRUE when AutostopActive == TRUE AND GearPosition != D

### SW-LL-FR-10: Engine Restart - Autostart (Functional)
The software must set EngineRestartRequest = TRUE when AutostopActive == TRUE AND TIME_AUTO_STOP >= 180000 ms

### SW-LL-FR-11: Enable / Disable (Functional)
The software must set SS_Enabled = TRUE when Start_Ignition == TRUE

### SW-LL-FR-12: Enable / Disable (Functional)
The software must toggle SS_Enabled when ButtonInput rising edge detected AND ButtonInput stable >= T_debounce ms (50ms)

### SW-LL-FR-13: Enable / Disable (Functional)
The software must reject button input when ButtonInput stable < T_debounce ms (50ms)

### SW-LL-FR-14: Enable / Disable (Functional)
The software must set AutostopAllowed = FALSE AND AutostartAllowed = FALSE when SS_Enabled == FALSE

### SW-LL-FR-15: Cluster (Functional)
The software must send a display message for 3s to the cluster when SS_Enabled != SS_Enabled_prev

### SW-LL-FR-16: Unavailable (Functional)
The software must set SS_Unavailable = TRUE when AutoStopAllowed == FALSE or AutoStartAllowed == FALSE

### SW-LL-FR-17: Cluster (Functional)
The software must command the instrument cluster to display the Start/Stop Unavailable indication when SS_Unavailable == TRUE

### SW-LL-FR-18: Cluster (Functional)
The software must command the instrument cluster to clear the Start/Stop Unavailable indication when SS_Unavailable == FALSE

### SW-LL-FR-19: Cluster (Functional)
The software must display AUTOSTOP_ACTIVE indicator in the cluster when AutostopActive == TRUE

### SW-LL-FR-20: HMI (Functional)
The software must set the Start/Stop HMI LED to OFF when SS_Enabled = TRUE

### SW-LL-FR-21: HMI (Functional)
The software must set the Start/Stop HMI LED to ON when SS_Enabled = FALSE

### SW-LL-FR-22: HMI (Functional)
The software must send a led update command to the HMI led when SS_Enabled != SS_Enabled_prev

### SW-LL-FR-23: CO₂ Estimation (Functional)
The software must increment TIME_AUTO_STOP by 100ms every control cycle when AutostopActive == TRUE

### SW-LL-FR-24: CO₂ Estimation (Functional)
The software must reset TIME_AUTO_STOP = 0 when IgnitionOFF == TRUE

### SW-LL-FR-25: CO₂ Estimation (Functional)
The software must compute CO2_AVOIDED = TIME_AUTO_STOP × WLTP_IDLE_FACTOR when AutostopActive == TRUE

### SW-LL-FR-26: CO₂ Estimation (Functional)
The software must command the cluster to display CO2_AVOIDED when AutostopActive == TRUE

### SW-LL-FR-27: CO₂ Estimation (Functional)
The software must command the cluster to hide CO2_AVOIDED when AutostopActive == FALSE

### SW-LL-FR-28: Safety Stop (Functional)
The software must set SafeStop = TRUE when (DoorStatus == OPEN or SeatBeltStatus == UNFASTENED) and AutoStopActive == TRUE

### SW-LL-FR-29: Engine Restart - Inhibition (Functional)
The software must inhibith AutoStart when SafeStop == TRUE

### SW-LL-FR-30: Engine Restart - Autostart (Functional)
The software must set EngineRestartRequest = TRUE when AnyAutoRestartConditions == TRUE and SafeStop == FALSE
